Spat-Descriptions {
  -- Definition of Vector Simple SPaT message
}

DEFINITIONS AUTOMATIC TAGS ::= 

BEGIN

SpatMessage ::= SEQUENCE {
    -- Information about actual state of traffic light
    trafficLightInfo TrafficLightInfo,
    position Position
}

TrafficLightInfo ::= SEQUENCE {
    trafficLightState   TrafficLightState,
    timeToChange      INTEGER (0..10000)
  }

TrafficLightState ::= ENUMERATED { 
    green      (0),
    yellow (1),
    red  (2)
} 

Position ::=  SEQUENCE {
   latitude Latitude,
   longitude Longitude
}

Latitude ::= SEQUENCE {
  hemisphere ENUMERATED { north (0), south (1) },
  degree  INTEGER (0..900000000) -- multiples of 0.1 microdegree
} 

Longitude ::= SEQUENCE {
  hemisphere ENUMERATED { east (0), west (1) },
  degree  INTEGER (0..1800000000) -- multiples of 0.1 microdegree
}

END
