ASN1Module DEFINITIONS AUTOMATIC TAGS ::= BEGIN

ASN1Protocol ::= SEQUENCE {
   booleanField       BOOLEAN OPTIONAL,
   bitStringField     BIT STRING { bit1(0), bit2(1) },
   sequenceField      SEQUENCE { enumeratedField  ENUMERATED { off (0), on (1) } },
   arrayField         SEQUENCE ( SIZE(0..10) ) OF SeperatlyDefinedChoice
}

SeperatlyDefinedChoice ::= CHOICE {
   numberChoice       INTEGER { namedNumber(123) },
   ia5StringChoice    IA5String
}

END
