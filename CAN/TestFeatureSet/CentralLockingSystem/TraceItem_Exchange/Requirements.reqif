# IBM Rational Requirements Thu Oct 01 10:29:28 CEST 2015

# Specification: Test Specifications
- Severity: Unclassified
- ReqIF.Name: Test Specifications
- Artefaktformat: Modul

## R6: HIL test
- Artefaktformat: Text
- Severity: Unclassified

### R5: static requirements
- Artefaktformat: Text
- Severity: Unclassified

#### R2: lock statically
Check if car is unlocked. Lock the car both when engine is off and when engine is running. Check if car is locked within expected time.
- Artefaktformat: Text
- Severity: Unclassified

#### R3: unlock statically
Check if car is locked. Unlock the car both when engine is off and when engine is running. Check if car is unlocked within expected time.
- Artefaktformat: Text
- Severity: Unclassified

### R4: velocity dependent requirements
- Severity: Unclassified
- Artefaktformat: Text

#### R1: lock by increasing velocity
Accelerate the velocity to a target speed, which is lower than the lock-velocity. The car should not be locked automatically. Accelerate the velocity to a target speed, which is higher than the lock-velocity. The car should be locked automatically.
- Severity: Unclassified
- Artefaktformat: Text

#### R7: no unlock by slowing down
Accelerate the velocity to a target speed, which is higher than the lock-velocity. The car should be locked automatically. Decelerate the velocity till stop. The car is still locked.
- Artefaktformat: Text
- Severity: Unclassified

#### R8: crash detection when car is moving
Accelerate the velocity to 60 km/h. The car should be locked automatically within expected time. Decelerate the velocity to 40 km/h. The car is still locked. Accelerate the velocity to 80 km/h and simulate a crash. The car should be unlocked automatically within expected time.
- Severity: Unclassified
- Artefaktformat: Text
